module ietf-pmip-qos {
    yang-version 1;

    namespace
      "urn:ietf:params:xml:ns:yang:ietf-pmip-qos";

    prefix "qos-pmip";

    import ietf-inet-types {
    	prefix inet;
    	revision-date 2013-07-15;
    }
    import ietf-traffic-selector-types { prefix traffic-selectors; }

    organization
      "IETF DMM (Dynamic Mobility Management) Working Group";

    contact
      "WG Web:   <https://datatracker.ietf.org/wg/dmm/>
     WG List:  <mailto:dmm@ietf.org>

     WG Chair: Dapeng Liu
               <mailto:maxpassion@gmail.com>

     WG Chair: Jouni Korhonen
               <mailto:jouni.nospam@gmail.com>

     Editor:
               <mailto:>";

    description
      "This module contains a collection of YANG definitions for
     quality of service paramaters used in Proxy Mobile IPv6.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module was created as part of the IETF
    	DMM FPC YANG modules; see the RFC itself for full legal notices.";

    revision 2016-02-10 {
        description "Initial revision";
        reference
         "RFC 7222: Quality-of-Service Option for Proxy Mobile IPv6";
    }

    // Type Definitions

    // QoS Option Field Type Definitions
	typedef sr-id {
		type uint8;
	    description
	     "An 8-bit unsigned integer used
	      for identifying the QoS Service Request.  Its uniqueness is within
	      the scope of a mobility session.  The local mobility anchor always
	      allocates the Service Request Identifier.  When a new QoS Service
	      Request is initiated by a mobile access gateway, the Service
	      Request Identifier in the initial request message is set to a
	      value of (0), and the local mobility anchor allocates a Service
	      Request Identifier and includes it in the response.  For any new
	      QoS Service Requests initiated by a local mobility anchor, the
	      Service Request Identifier is set to the allocated value.";
	  }

    typedef traffic-class {
    	type inet:dscp;
    	description
    		"Traffic Class consists of a 6-bit DSCP field followed by a 2-bit
    		reserved field.";
	   reference
		     "RFC 3289: Management Information Base for the Differentiated
		                Services Architecture
		      RFC 2474: Definition of the Differentiated Services Field
		                (DS Field) in the IPv4 and IPv6 Headers
		      RFC 2780: IANA Allocation Guidelines For Values In
		                the Internet Protocol and Related Headers";
    }

    typedef operational-code {
    	type enumeration {
    		enum RESPONSE { value 0; }
    		enum ALLOCATE { value 1; }
    		enum DE-ALLOCATE { value 2; }
    		enum MODIFY { value 3; }
    		enum QUERY { value 4; }
    		enum NEGOTIATE { value 5; }
    	}
    	description
    		"1-octet Operational code indicates the type of QoS request.

    	      RESPONSE:   (0)
    	         Response to a QoS request

    	      ALLOCATE:   (1)
    	         Request to allocate QoS resources

    	      DE-ALLOCATE:   (2)
    	         Request to de-Allocate QoS resources

    	      MODIFY:   (3)
    	         Request to modify QoS parameters for a previously negotiated
    	         QoS Service Request

    	      QUERY:   (4)
    	         Query to list the previously negotiated QoS Service Requests
    	         that are still active

    	      NEGOTIATE:   (5)
                Response to a QoS Service Request with a counter QoS proposal

              Reserved:   (6) to (255)
                Currently not used.  Receiver MUST ignore the option received
                with any value in this range.";
    }

    // QoS Attribute Types

    //The enumeration value for mapping - don't confuse with the identities
    typedef qos-attrubite-type-enum {
    	type enumeration {
    		enum Reserved { value 0; }
    		enum Per-MN-Agg-Max-DL-Bit-Rate { value 1; }
	        enum Per-MN-Agg-Max-UL-Bit-Rate { value 2; }
	        enum Per-Session-Agg-Max-DL-Bit-Rate { value 3; }
	        enum Per-Session-Agg-Max-UL-Bit-Rate { value 4; }
          enum Allocation-Retention-Priority { value 5; }
	      	enum Aggregate-Max-DL-Bit-Rate { value 6; }
	        enum Aggregate-Max-UL-Bit-Rate { value 7; }
	        enum Guaranteed-DL-Bit-Rate { value 8; }
	        enum Guaranteed-UL-Bit-Rate { value 9; }
	        enum QoS-Traffic-Selector { value 10; }
	        enum QoS-Vendor-Specific-Attribute { value 11; }
    	}
 		description
		"8-bit unsigned integer indicating the type of the QoS
	      attribute.  This specification reserves the following values.
	      (0) -  Reserved
	         This value is reserved and cannot be used

	      (1) -  Per-MN-Agg-Max-DL-Bit-Rate
	         Per-Mobile-Node Aggregate Maximum Downlink Bit Rate.

	      (2) -  Per-MN-Agg-Max-UL-Bit-Rate
	         Per-Mobile-Node Aggregate Maximum Uplink Bit Rate.

	      (3) -  Per-Session-Agg-Max-DL-Bit-Rate
	         Per-Mobility-Session Aggregate Maximum Downlink Bit Rate.

		    (4) -  Per-Session-Agg-Max-UL-Bit-Rate
              Per-Mobility-Session Aggregate Maximum Uplink Bit Rate.

 	      (5) -  Allocation-Retention-Priority
 	         Allocation and Retention Priority.

 	      (6) -  Aggregate-Max-DL-Bit-Rate
 	         Aggregate Maximum Downlink Bit Rate.

 	      (7) -  Aggregate-Max-UL-Bit-Rate
 	         Aggregate Maximum Uplink Bit Rate.

 	      (8) -  Guaranteed-DL-Bit-Rate
 	         Guaranteed Downlink Bit Rate.

 	      (9) -  Guaranteed-UL-Bit-Rate
 	         Guaranteed Uplink Bit Rate.

 	      (10) -  QoS-Traffic-Selector
 	         QoS Traffic Selector.

 	      (11) -  QoS-Vendor-Specific-Attribute
 	        QoS Vendor-Specific Attribute.

 	      (12) to (254) -  Reserved
 	         These values are reserved for future allocation.

 	      (255) -  Reserved
 	         This value is reserved and cannot be used.";
    }

    // Attribute Type as Identities
    // Added for convenience of inclusion and extension in other YANG modules.
    identity qos-attribute-type {
    	description
    		"Base type for Quality of Service Attributes";
    }

    identity Per-MN-Agg-Max-DL-Bit-Rate-type {
    	base qos-attribute-type;
    	description
    		"Per-Mobile-Node Aggregate Maximum Downlink Bit Rate.";
	}

 	identity Per-MN-Agg-Max-UL-Bit-Rate-type {
    	base qos-attribute-type;
    	description
    		"Per-Mobile-Node Aggregate Maximum Uplink Bit Rate";
 	}

 	identity Per-Session-Agg-Max-DL-Bit-Rate-type {
    	base qos-attribute-type;
    	description
    		"Per-Mobility-Session Aggregate Maximum Downlink Bit Rate.";
 	}

 	identity Per-Session-Agg-Max-UL-Bit-Rate-type {
    	base qos-attribute-type;
    	description
    		"Per-Mobility-Session Aggregate Maximum Uplink Bit Rate.";
 	}

 	identity Allocation-Retention-Priority-type {
    	base qos-attribute-type;
    	description
    		"Allocation and Retention Priority.";
 	}

 	identity Aggregate-Max-DL-Bit-Rate-type {
	  	base qos-attribute-type;
	  	description "Aggregate Maximum Downlink Bit Rate.";
 	}

  identity Aggregate-Max-UL-Bit-Rate-type {
      base qos-attribute-type;
      description "Aggregate Maximum Uplink Bit Rate.";
  }

  identity Guaranteed-DL-Bit-Rate-type {
      base qos-attribute-type;
      description "Guaranteed Downlink Bit Rate.";
  }

  identity Guaranteed-UL-Bit-Rate-type {
      base qos-attribute-type;
      description "Guaranteed Uplink Bit Rate.";
  }

  identity QoS-Traffic-Selector-type {
      base qos-attribute-type;
      description "QoS Traffic Selector.";
  }

  identity QoS-Vendor-Specific-Attribute-type {
      base qos-attribute-type;
      description "QoS Vendor-Specific Attribute.";
  }

  //value definitions
  typedef Per-MN-Agg-Max-DL-Bit-Rate-Value {
      type uint32;
      description
          "This is a 32-bit unsigned integer that
          indicates the aggregate maximum downlink bit rate that is
          requested/allocated for all the mobile node's IP flows.  The
          measurement units for Per-MN-Agg-Max-DL-Bit-Rate are bits per
          second.";
	}

 	typedef Per-MN-Agg-Max-UL-Bit-Rate-Value {
    	type uint32;
    	description
    		"This is a 32-bit unsigned integer that
    	      indicates the aggregate maximum uplink bit rate that is requested/
    	      allocated for the mobile node's IP flows.  The measurement units
    	      for Per-MN-Agg-Max-UL-Bit-Rate are bits per second.";
 	}

 	// Generic Structure for the uplink and downlink
 	grouping Per-Session-Agg-Max-Bit-Rate-Value {
 		leaf max-rate {
 			type uint32;
 			mandatory true;
 			description
 				"This is a 32-bit unsigned integer
 			      that indicates the aggregate maximum bit rate that is requested/allocated
 				  for all the IP flows associated with that mobility session.  The measurement
 				  units for Per-Session-Agg-Max-UL/DL-Bit-Rate are bits per second.";
 		}
 		leaf service-flag {
			type boolean;
			mandatory true;
			description
				"This flag is used for extending the scope of the
			      target flows for Per-Session-Agg-Max-UL/DL-Bit-Rate from(UL)/to(DL) the mobile
			      node's other mobility sessions sharing the same Service
			      Identifier. 3GPP Access Point Name (APN) is an example of a
			      Service Identifier, and that identifier is carried using the
			      Service Selection mobility option [RFC5149].

			      *  When the (S) flag is set to a value of (1), then the Per-
			         Session-Agg-Max-Bit-Rate is measured as an aggregate across
			         all the mobile node's other mobility sessions sharing the same
			         Service Identifier associated with this mobility session.

			      *  When the (S) flag is set to a value of (0), then the target
			         flows are limited to the current mobility session.

			      *  The (S) flag MUST NOT be set to a value of (1) when there is no
			         Service Identifier associated with the mobility session.";
			reference
				"RFC 5149 - Service Selection mobility option";
 		}
 		leaf exclude-flag {
 			type boolean;
 			mandatory true;
 			description
 				"This flag is used to request that the uplink/downlink
 			      flows for which the network is providing Guaranteed-Bit-Rate
 			      service be excluded from the target IP flows for which Per-
 			      Session-Agg-Max-UL/DL-Bit-Rate is measured.

 			      *  When the (E) flag is set to a value of (1), then the request is
 			         to exclude the IP flows for which Guaranteed-UL/DL-Bit-Rate
 			         is negotiated from the flows for which Per-Session-Agg-Max-UL/DL-Bit-Rate
 				     is measured.

 			      *  When the (E) flag is set to a value of (0), then the request is
 			         not to exclude any IP flows from the target IP flows for which
 			         Per-Session-Agg-Max-UL/DL-Bit-Rate is measured.

 			      *  When the (S) flag and (E) flag are both set to a value of (1),
 			         then the request is to exclude all the IP flows sharing the
 			         Service Identifier associated with this mobility session from
 			         the target flows for which Per-Session-Agg-Max-UL/DL-Bit-Rate is
 			         measured.";
 		}
 	}

 	grouping Allocation-Retention-Priority-Value {
 		leaf prioirty-level {
 			type uint8 {
 				range "0..15";
 			}
 			mandatory true;
 			description
 				"This is a 4-bit unsigned integer value.  It
 			      is used to decide whether a mobility session establishment or
 			      modification request can be accepted; this is typically used for
 			      admission control of Guaranteed Bit Rate traffic in case of
 			      resource limitations.  The priority level can also be used to

 			      decide which existing mobility session to preempt during resource
 			      limitations.  The priority level defines the relative timeliness
 			      of a resource request.

 			      Values 1 to 15 are defined, with value 1 as the highest level of
 			      priority.

 			      Values 1 to 8 should only be assigned for services that are
 			      authorized to receive prioritized treatment within an operator
 			      domain.  Values 9 to 15 may be assigned to resources that are
 			      authorized by the home network and thus applicable when a mobile
 			      node is roaming.";
 		}
 		leaf premption-capability {
 			type enumeration {
				enum enabled { value 0; }
				enum disabled { value 1; }
				enum reserved1 { value 2; }
				enum reserved2 { value 3; }
 			}
 			mandatory true;
 			description
 				"This is a 2-bit unsigned integer
 			      value.  It defines whether a service data flow can get resources
 			      that were already assigned to another service data flow with a
 			      lower priority level.  The following values are defined:

 			         Enabled (0): This value indicates that the service data flow is
 			         allowed to get resources that were already assigned to another
 			         IP data flow with a lower priority level.

 			         Disabled (1): This value indicates that the service data flow
 			         is not allowed to get resources that were already assigned to
 			         another IP data flow with a lower priority level.  The values
 			         (2) and (3) are reserved.";
 		}
 		leaf premption-vulnerability {
 			type enumeration {
				enum enabled { value 0; }
				enum disabled { value 1; }
				enum reserved1 { value 2; }
				enum reserved2 { value 3; }
 			}
 			mandatory true;
 			description
				"This is a 2-bit unsigned integer
 			      value.  It defines whether a service data flow can lose the
 			      resources assigned to it in order to admit a service data flow
 			      with a higher priority level.  The following values are defined:

 			         Enabled (0): This value indicates that the resources assigned
 			         to the IP data flow can be preempted and allocated to a service
 			         data flow with a higher priority level.

 			         Disabled (1): This value indicates that the resources assigned
 			         to the IP data flow shall not be preempted and allocated to a
 			         service data flow with a higher priority level.  The values (2)
 			         and (3) are reserved.";
 		}
 	}

 	typedef Aggregate-Max-DL-Bit-Rate-Value {
	  	type uint32;
	  	description
	  		"This is a 32-bit unsigned integer that
	        indicates the aggregate maximum downlink bit rate that is
	        requested/allocated for downlink IP flows.  The measurement units
	        for Aggregate-Max-DL-Bit-Rate are bits per second.";
 	}

  	typedef Aggregate-Max-UL-Bit-Rate-Value {
    	type uint32;
    	description
    		"This is a 32-bit unsigned integer that
    	      indicates the aggregate maximum downlink bit rate that is
    	      requested/allocated for downlink IP flows.  The measurement units
    	      for Aggregate-Max-DL-Bit-Rate are bits per second.";
  	}

  	typedef Guaranteed-DL-Bit-Rate-Value {
	  	type uint32;
	  	description
	  		"This is a 32-bit unsigned integer that
	        indicates the guaranteed bandwidth in bits per second for downlink
	        IP flows.  The measurement units for Guaranteed-DL-Bit-Rate are
	        bits per second.";
  	}

  	typedef Guaranteed-UL-Bit-Rate-Value {
    	type uint32;
    	description
    		"This is a 32-bit unsigned integer that
    	      indicates the guaranteed bandwidth in bits per second for uplink
    	      IP flows.  The measurement units for Guaranteed-UL-Bit-Rate are
    	      bits per second.";
  	}

  	grouping QoS-Vendor-Specific-Attribute-Value-Base {
  		leaf vendorid {
  			type uint32;
  			mandatory true;
  			description
  				"The Vendor ID is the SMI (Structure of Management
  		      Information) Network Management Private Enterprise Code of the
  		      IANA-maintained 'Private Enterprise Numbers' registry [SMI].";
  			reference
  				"'PRIVATE ENTERPRISE NUMBERS', SMI Network Management
                Private Enterprise Codes, April 2014,
                <http://www.iana.org/assignments/enterprise-numbers>";
  		}
  		leaf subtype {
  			type uint8;
  			mandatory true;
  			description
  				"An 8-bit field indicating the type of vendor-specific
  		      information carried in the option.  The namespace for this sub-
  		      type is managed by the vendor identified by the Vendor ID field.";
  		}
    	description
    		"QoS Vendor-Specific Attribute.";
  	}

    //NOTE - We do NOT add the Status Codes or other changes in PMIP in this module

  	//Primary Structures (groupings)
    grouping qosattribute {
        leaf attributetype {
            type identityref {
                base qos-attribute-type;
            }
            mandatory true;
            description "the attribute type";
        }

  		  //All of the sub-types by constraint
        choice attribute-choice {
            case per-mn-agg-max-dl-case {
                when "../attributetype = 'Per-MN-Agg-Max-DL-Bit-Rate-type'";
                leaf per-mn-agg-max-dl {
                    type qos-pmip:Per-MN-Agg-Max-DL-Bit-Rate-Value;
                }
            }
            case per-mn-agg-max-ul-case {
                when "../attributetype = 'Per-MN-Agg-Max-UL-Bit-Rate-type'";
                leaf per-mn-agg-max-ul {
                    type qos-pmip:Per-MN-Agg-Max-UL-Bit-Rate-Value;
                }
            }
            case per-session-agg-max-dl-case {
                when "../attributetype = 'Per-Session-Agg-Max-DL-Bit-Rate-type'";
                container per-session-agg-max-dl {
                    uses qos-pmip:Per-Session-Agg-Max-Bit-Rate-Value;
                }
            }
            case per-session-agg-max-ul-case {
                when "../attributetype = 'Per-Session-Agg-Max-UL-Bit-Rate-type'";
                container per-session-agg-max-ul {
                    uses qos-pmip:Per-Session-Agg-Max-Bit-Rate-Value;
                }
            }
            case allocation-retention-priority-case {
                when "../attributetype = 'Allocation-Retention-Priority-type'";
                uses qos-pmip:Allocation-Retention-Priority-Value;
            }
            case agg-max-dl-case {
                when "../attributetype = 'Aggregate-Max-DL-Bit-Rate-type'";
                leaf agg-max-dl {
                    type qos-pmip:Aggregate-Max-DL-Bit-Rate-Value;
                }
            }
            case agg-max-ul-case {
                when "../attributetype = 'Aggregate-Max-UL-Bit-Rate-type'";
                leaf agg-max-ul {
                    type qos-pmip:Aggregate-Max-UL-Bit-Rate-Value;
                }
            }
            case gbr-dl-case {
                when "../attributetype = 'Guaranteed-DL-Bit-Rate-type'";
                leaf gbr-dl {
                    type qos-pmip:Guaranteed-DL-Bit-Rate-Value;
                }
            }
            case gbr-ul-case {
                when "../attributetype = 'Guaranteed-UL-Bit-Rate-type'";
                leaf gbr-ul {
                    type qos-pmip:Guaranteed-UL-Bit-Rate-Value;
                }
            }
            case traffic-selector-case {
                when "../attributetype = 'QoS-Traffic-Selector-type'";
                container traffic-selector {
                    uses traffic-selectors:traffic-selector;
                }
            }
        }
    }

  	grouping qosoption {
        leaf srid {
            type sr-id;
            mandatory true;
        }
        leaf trafficclass {
            type traffic-class;
            mandatory true;
        }
        leaf operationcode {
            type operational-code;
            mandatory true;
        }
        list attributes {
            unique "attributetype";
            uses qosattribute;
            min-elements 1;
        }
  	}
}
