module ietf-dmm-fpc-policyext {
    namespace "urn:ietf:params:xml:ns:yang:fpcpolicyext";
    prefix fpcpolicyext;

    import ietf-inet-types { prefix inet; revision-date 2013-07-15; }

    organization "IETF DMM Working Group";
    contact "Satoru Matsushima <satoru.matsushima@g.softbank.co.jp>";

    description
    "This module contains YANG definition for
     Forwarding Policy Configuration Protocol (FPCP)
     common Policy Action and Descriptor extensions";

    revision 2016-08-03 {
        description "Changes based on -04 version of FPC draft.";
        reference "draft-ietf-dmm-fpc-cpdp-04";
    }

    grouping simple-nat {
      leaf outbound-nat-address {
        type inet:ip-address;
      }
    }

    grouping simple-napt {
      leaf source-port {
        type inet:port-number;
      }
      leaf outbound-napt-address {
        type inet:ip-address;
      }
      leaf destination-port {
        type inet:port-number;
      }
    }

    grouping prefix-traffic-descriptor {
        description
        "Traffic descriptor group collects parameters to
         identify target traffic flow.  It represents
         source/destination as IP prefixes";

        leaf destination-ip {
            type inet:ip-prefix;
            description "Rule of destination IP";
        }
        leaf source-ip {
            type inet:ip-prefix;
            description "Rule of source IP";
        }
    }

    grouping rating-action {
      description "Rudimentary rating action applied based upon RFC 4006 attributes";
      leaf service-context-id {
        type string;
        description "Per RFC 4006 - Contains a unique identifier of the Diameter credit-control service
           specific document that applies to the request.  The format of the Service-Context-Id is:

           <service-context>@<domain>

           service-context = Token

         The Token is an arbitrary string of characters and digits.

         'domain' represents the entity that allocated the Service-Context-Id.";
      }
      leaf service-identifier {
        type uint32;
        description "From RFC 4006 - Contains the identifier of a service.  The specific service the
           request relates to is uniquely identified by the combination of
           Service-Context-Id and Service-Identifier AVPs.";
      }
      leaf rating-group {
        type uint32;
        description "From RFC 4006 - Contains the identifier of a rating group.  All the services subject
           to the same rating type are part of the same rating group.  The
           specific rating group the request relates to is uniquely identified
           by the combination of Service-Context-Id and Rating-Group AVPs.";
      }
    }

    grouping domain-descriptor-list {
      description "Descriptors for list of domains";
      leaf-list source-domains {
          type inet:domain-name;
          description "Source Domain Names";
      }
      leaf-list destination-domains {
          type inet:domain-name;
          description "Destination Domain Names";
      }
    }
}
